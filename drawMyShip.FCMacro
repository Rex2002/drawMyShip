import FreeCAD as App

import Part
import Sketcher
import Draft



doc = App.activeDocument()
body = doc.ActiveObject
WL_heights = [100,200,300,400, 500, 600]
cFrames_distances = [0, 1000, 2000, 3000, 4000, 5000, 6000, 7000, 8000]
cFrames = [
#    cf1  cf2   cf3  cf4  cf5  cf6  cf7  cf8  cf9
    [150, 250,  200, 200, 200, 200, 200, 200, 200], #Breadth at WL1
    [250, 750,  500, 500, 500, 500, 500, 500, 500], #Breadth at WL2
    [500, 1000, 750, 750, 750, 750, 750, 750, 750], #Breadth at WL3
    [500, 1000, 750, 750, 750, 750, 750, 750, 750], #Breadth at WL4
    [500, 1000, 750, 750, 750, 750, 750, 750, 750], #Breadth at WL5
    [500, 1000, 750, 750, 750, 750, 750, 750, 750], #Breadth at WL6
]
sponung = [
    25, 20, 15, 10, 5, 0, 2,4,6, #Height above Base
]


def createCurve(pointsList):
    curve = Part.BSplineCurve()
    curve.interpolate([point for point in pointsList])
    curve.increaseDegree(3)
        
    return Part.BSplineCurve(curve.getPoles(), curve.getMultiplicities(), curve.getKnots(), False, 3, None, False)


cFrameSplineSketches = []
cFramePlanes = []
for frame in range(len(cFrames[0])):
    print("frame: " + str(frame))
    refPlane = doc.addObject("PartDesign::Plane", "cFramePlane" + str(frame))
    refPlane.AttachmentSupport = [(doc.getObject("YZ_Plane"), [""])]
    refPlane.MapMode = "FlatFace"
    refPlane.Placement = App.Placement(App.Vector(0,cFrames_distances[frame],0), App.Rotation(0,0,90))
    refPlane.Visibility = True
    cFramePlanes.append(refPlane)
    sketch = doc.addObject("Sketcher::SketchObject", "Frame" + str(frame))
    

    sketch.AttachmentSupport = [(doc.getObject("cFramePlane" + str(frame)), '')]
    sketch.MapMode = "FlatFace"

    points = [App.Vector(0,sponung[frame],0)]

    for WL in range(len(cFrames)):
        points.append(App.Vector(-cFrames[WL][frame], WL_heights[WL], 0))

    for WL in range(len(cFrames)):
        points.insert(0,App.Vector(cFrames[WL][frame],WL_heights[WL], 0))
    for point in points:
        sketch.addGeometry(Part.Point(point), False)
    cFrameSplineSketches.append([sketch, createCurve(points)])
for sketch, cFrameSpline in cFrameSplineSketches:
    sketch.addGeometry(cFrameSpline, False)
'''points = []
points.append(App.Vector(3,1,0))
points.append(App.Vector(2,2,0))
points.append(App.Vector(1,3,0))
curve = Part.BSplineCurve()
curve.interpolate(points)
sketch.addGeometry(curve)
sketch.addGeometry(Part.LineSegment(App.Vector(1.2, 1.8, 0),
                                    App.Vector(5.2, 5.3, 0)), False)
sketch.addGeometry(Part.LineSegment(App.Vector(6.5, 1.5, 0),
                                    App.Vector(10.2, 5.0, 0)), False)
sketch.addGeometry(Part.LineSegment(App.Vector(12.2, 1.0, 0),
                                    App.Vector(15.4, 5.0, 0)), False)
'''
doc.recompute()
